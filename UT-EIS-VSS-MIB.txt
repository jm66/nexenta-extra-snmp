---------------------------------------------------------------
-- University of Toronto, EIS. VSS base MIB.
---------------------------------------------------------------

UT-EIS-VSS-MIB DEFINITIONS ::= BEGIN

IMPORTS
    enterprises, MODULE-IDENTITY FROM SNMPv2-SMI;

uteisvssMIB MODULE-IDENTITY
    LAST-UPDATED "201511190000Z"
    ORGANIZATION "University of Toronto, EIS"
    CONTACT-INFO
    	 "postal:   Enterprise Infrastructure Solutions
    	            255 Huron St. Room 368,
    	            Toronto, ON, CA
          email:    vss@eis.utoronto.ca"
    DESCRIPTION
            "MIB that defines the VSS custom perf counters"
    REVISION     "201511190000Z"
    DESCRIPTION
            "Initial version"

    ::= { enterprises 6973 }

core OBJECT IDENTIFIER ::= { uteisvssMIB 1 }
storage OBJECT IDENTIFIER ::= { core 1 }
iostat OBJECT IDENTIFIER ::= { storage 1 }
nfs OBJECT IDENTIFIER ::= { storage 2 }
zfs OBJECT IDENTIFIER ::= { storage 3}

END
