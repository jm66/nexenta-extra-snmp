NYMNETWORKS-MIB DEFINITIONS ::= BEGIN

IMPORTS
	enterprises FROM RFC1155-SMI
	OBJECT-TYPE FROM RFC-1212
	DisplayString FROM RFC-1213;

nymnetworks	OBJECT IDENTIFIER ::= {enterprises 25359}

zfs	OBJECT IDENTIFIER ::= {nymnetworks 1}
ipmi	OBJECT IDENTIFIER ::= {nymnetworks 2}
ups	OBJECT IDENTIFIER ::= {nymnetworks 3}
fs      OBJECT IDENTIFIER ::= {zfs 1}
vols 	OBJECT IDENTIFIER ::= {zfs 5}
fss	OBJECT IDENTIFIER ::= {zfs 6}

zfsFilesystemTName OBJECT-TYPE
        SYNTAX  DisplayString
        ACCESS  read-only
        STATUS  mandatory
        DESCRIPTION
                "The name of the filesystem type FilesystemT."
        ::= {fss 1}

zfsFilesystemTAvailableKB OBJECT-TYPE
        SYNTAX  GAUGE
        ACCESS  read-only
        STATUS  mandatory
        DESCRIPTION
                 "The number of 1 KB blocks that are available for use."
        ::= {fss 2}

zfsFilesystemTUsedKB OBJECT-TYPE
        SYNTAX  GAUGE
        ACCESS  read-only
        STATUS  mandatory
        DESCRIPTION
                 "The number of 1 KB blocks that are in use."
        ::= {fss 3}

zfsFilesystemTSizeKB OBJECT-TYPE
        SYNTAX  GAUGE
        ACCESS  read-only
        STATUS  mandatory
        DESCRIPTION
                 "The number of 1 KB blocks of the volume."
        ::= {fss 4}

zfsFilesystemTAvailableMB OBJECT-TYPE
        SYNTAX  GAUGE
        ACCESS  read-only
        STATUS  mandatory
        DESCRIPTION
                 "The number of 1 MB blocks that are available for use.
                 Useful if zfsFilesystemTAvailableKB exceeds a 32 bit
                 integer."
        ::= {fss 12}

zfsFilesystemTUsedMB OBJECT-TYPE
        SYNTAX  GAUGE
        ACCESS  read-only
        STATUS  mandatory
        DESCRIPTION
                 "The number of 1 MB blocks that are in use Useful if
                 zfsFilesystemTUsedKB exceeds a 32 bit integer."
        ::= {fss 13}

zfsFilesystemTSizeMB OBJECT-TYPE
        SYNTAX  GAUGE
        ACCESS  read-only
        STATUS  mandatory
        DESCRIPTION
                 "The number of 1 MB blocks part of the volume Useful if
                 zfsFilesystemTSizeKB exceeds a 32 bit integer."
        ::= {fss 14}

zfsVolumeName OBJECT-TYPE
        SYNTAX  DisplayString
        ACCESS  read-only
        STATUS  mandatory
        DESCRIPTION
                "The name of the filesystem type Volume."
        ::= {vols 1}

zfsVolumeAvailableKB OBJECT-TYPE
        SYNTAX  GAUGE
        ACCESS  read-only
        STATUS  mandatory
        DESCRIPTION
                 "The number of 1 KB blocks that are available for use."
        ::= {vols 2}

zfsVolumeUsedKB OBJECT-TYPE
        SYNTAX  GAUGE
        ACCESS  read-only
        STATUS  mandatory
        DESCRIPTION
                 "The number of 1 KB blocks that are in use."
        ::= {vols 3}

zfsVolumeSizeKB OBJECT-TYPE
        SYNTAX  GAUGE
        ACCESS  read-only
        STATUS  mandatory
        DESCRIPTION
                 "The number of 1 KB blocks of the volume."
        ::= {vols 4}

zfsVolumeAvailableMB OBJECT-TYPE
        SYNTAX  GAUGE
        ACCESS  read-only
        STATUS  mandatory
        DESCRIPTION
                 "The number of 1 MB blocks that are available for use.
                 Useful if zfsVolumeAvailableKB exceeds a 32 bit
                 integer."
        ::= {vols 12}

zfsVolumeUsedMB OBJECT-TYPE
        SYNTAX  GAUGE
        ACCESS  read-only
        STATUS  mandatory
        DESCRIPTION
                 "The number of 1 MB blocks that are in use Useful if
                 zfsVolumeUsedKB exceeds a 32 bit integer."
        ::= {vols 13}

zfsVolumeSizeMB OBJECT-TYPE
        SYNTAX  GAUGE
        ACCESS  read-only
        STATUS  mandatory
        DESCRIPTION
                 "The number of 1 MB blocks part of the volume Useful if
                 zfsVolumeSizeKB exceeds a 32 bit integer."
        ::= {vols 14}

zfsFilesystemName OBJECT-TYPE
	SYNTAX	DisplayString
	ACCESS	read-only
	STATUS	mandatory
	DESCRIPTION
		"The name of the filesystem."
	::= {fs 1}

zfsFilesystemAvailableKB OBJECT-TYPE
	SYNTAX	GAUGE
	ACCESS	read-only
	STATUS	mandatory
	DESCRIPTION
	         "The number of 1 KB blocks that are available for use."
	::= {fs 2}

zfsFilesystemUsedKB OBJECT-TYPE
	SYNTAX	GAUGE
	ACCESS	read-only
	STATUS	mandatory
	DESCRIPTION
	         "The number of 1 KB blocks that are in use."
	::= {fs 3}

zfsPoolHealth OBJECT-TYPE
	SYNTAX	INTEGER { online(1), degraded(2), faulted(3), unknown(4) }
	ACCESS	read-only
	STATUS	mandatory
	DESCRIPTION
	         "The current health of the containing pool, as reported
		 by zpool status."
	::= {fs 4}

zfsFilesystemSizeKB OBJECT-TYPE
        SYNTAX  INTEGER { online(1), degraded(2), faulted(3), unknown(4) }
        ACCESS  read-only
        STATUS  mandatory
        DESCRIPTION
        	 "The number of 1 MB blocks that are assigned"
	::= {fs 5}

zfsFilesystemAvailableMB OBJECT-TYPE
	SYNTAX	GAUGE
	ACCESS	read-only
	STATUS	mandatory
	DESCRIPTION
	         "The number of 1 MB blocks that are available for use.
		 Useful if zfsFilesystemAvailableKB exceeds a 32 bit
		 integer."
	::= {fs 12}

zfsFilesystemUsedMB OBJECT-TYPE
	SYNTAX	GAUGE
	ACCESS	read-only
	STATUS	mandatory
	DESCRIPTION
	         "The number of 1 MB blocks that are in use Useful if
		 zfsFilesystemUsedKB exceeds a 32 bit integer."
	::= {fs 13}

zfsFilesystemSizeMB OBJECT-TYPE
        SYNTAX  GAUGE
        ACCESS  read-only
        STATUS  mandatory
        DESCRIPTION
                 "The number of 1 MB blocks that are assigned  Useful if
                 zfsFilesystemSizeKB exceeds a 32 bit integer."
        ::= {fs 14}

arc	OBJECT IDENTIFIER ::= {zfs 2}

zfsARCSizeKB OBJECT-TYPE
	SYNTAX	GAUGE
	ACCESS	read-only
	STATUS	mandatory
	DESCRIPTION
	         "The current ARC size in KB."
	::= {arc 1}

zfsARCMetadataSizeKB OBJECT-TYPE
	SYNTAX	GAUGE
	ACCESS	read-only
	STATUS	mandatory
	DESCRIPTION
	         "The amount of ARC space used for metadata storage, in KB."
	::= {arc 2}

zfsARCDataSizeKB OBJECT-TYPE
	SYNTAX	GAUGE
	ACCESS	read-only
	STATUS	mandatory
	DESCRIPTION
	         "The amount of ARC space used for file data storage, in KB."
	::= {arc 3}

zfsARCHits OBJECT-TYPE
	SYNTAX	COUNTER
	ACCESS	read-only
	STATUS	mandatory
	DESCRIPTION
	         "The number of ARC accesses that were cache hits."
	::= {arc 4}

zfsARCMisses OBJECT-TYPE
	SYNTAX	GAUGE
	ACCESS	read-only
	STATUS	mandatory
	DESCRIPTION
	         "The number of ARC accesses that were cache misses."
	::= {arc 5}

zfsARCTargetSize OBJECT-TYPE
        SYNTAX  GAUGE
        ACCESS  read-only
        STATUS  mandatory
        DESCRIPTION
                 "The amount of ARC Target size"
        ::= {arc 6}

zfsARCMru OBJECT-TYPE
        SYNTAX  GAUGE
        ACCESS  read-only
        STATUS  mandatory
        DESCRIPTION
                 "The amount of ARC size most recently used."
        ::= {arc 7}
l2arc	OBJECT IDENTIFIER ::= {zfs 3}

zfsL2ARCHits OBJECT-TYPE
	SYNTAX	COUNTER
	ACCESS	read-only
	STATUS	mandatory
	DESCRIPTION
	         "The number of L2ARC accesses that were cache hits."
	::= {l2arc 1}

zfsL2ARCMisses OBJECT-TYPE
	SYNTAX	COUNTER
	ACCESS	read-only
	STATUS	mandatory
	DESCRIPTION
	         "The number of L2ARC accesses that were cache misses."
	::= {l2arc 2}

zfsL2ARCReads OBJECT-TYPE
	SYNTAX	COUNTER
	ACCESS	read-only
	STATUS	mandatory
	DESCRIPTION
	         "The number of reads made from L2ARC devices."
	::= {l2arc 3}

zfsL2ARCWrites OBJECT-TYPE
	SYNTAX	COUNTER
	ACCESS	read-only
	STATUS	mandatory
	DESCRIPTION
	         "The number of writes made to L2ARC devices."
	::= {l2arc 4}

io	OBJECT IDENTIFIER ::= {zfs 4}

zfsReadKB OBJECT-TYPE
	SYNTAX	COUNTER
	ACCESS	read-only
	STATUS	mandatory
	DESCRIPTION
	         "The amount of file data read from the ZFS filesystem layer, in KB."
	::= {io 1}

zfsReaddirKB OBJECT-TYPE
	SYNTAX	COUNTER
	ACCESS	read-only
	STATUS	mandatory
	DESCRIPTION
	         "The amount of directory data read from the ZFS filesystem layer, in KB."
	::= {io 2}

zfsWriteKB OBJECT-TYPE
	SYNTAX	COUNTER
	ACCESS	read-only
	STATUS	mandatory
	DESCRIPTION
	         "The amount of file data written to the ZFS filesystem layer, in KB."
	::= {io 3}

temperature	OBJECT IDENTIFIER ::= {ipmi 1}

tempSensorName OBJECT-TYPE
	SYNTAX	DisplayString
	ACCESS	read-only
	STATUS	mandatory
	DESCRIPTION
	         "The name of the designated temperature sensor."
	::= {temperature 1}

tempSensorValue OBJECT-TYPE
	SYNTAX	GAUGE
	ACCESS	read-only
	STATUS	mandatory
	DESCRIPTION
	         "The current value of the designated temperature sensor."
	::= {temperature 2}


upsId OBJECT-TYPE
	SYNTAX	DisplayString
	ACCESS	read-only
	STATUS	mandatory
	DESCRIPTION
	         "The UPS identifier."
	::= {ups 1}

upsModel OBJECT-TYPE
	SYNTAX	DisplayString
	ACCESS	read-only
	STATUS	mandatory
	DESCRIPTION
	         "The UPS model name."
	::= {ups 2}

upsManufacturer OBJECT-TYPE
	SYNTAX	DisplayString
	ACCESS	read-only
	STATUS	mandatory
	DESCRIPTION
	         "The UPS manufacturer name."
	::= {ups 3}

upsSerial OBJECT-TYPE
	SYNTAX	DisplayString
	ACCESS	read-only
	STATUS	mandatory
	DESCRIPTION
	         "The UPS serial number."
	::= {ups 4}

upsBatteryChargePercent OBJECT-TYPE
	SYNTAX	GAUGE
	ACCESS	read-only
	STATUS	mandatory
	DESCRIPTION
	         "The current battery charge in percent."
	::= {ups 5}

upsBatteryRuntimeSec OBJECT-TYPE
	SYNTAX	GAUGE
	ACCESS	read-only
	STATUS	mandatory
	DESCRIPTION
	         "The current remaining runtime in seconds."
	::= {ups 6}

upsBatteryVoltagedV OBJECT-TYPE
	SYNTAX	GAUGE
	ACCESS	read-only
	STATUS	mandatory
	DESCRIPTION
	         "The current battery voltage in dV."
	::= {ups 7}

upsBatteryNominalVoltagedV OBJECT-TYPE
	SYNTAX	GAUGE
	ACCESS	read-only
	STATUS	mandatory
	DESCRIPTION
	         "The nominal battery voltage in dV."
	::= {ups 8}

upsBatteryType OBJECT-TYPE
	SYNTAX	DisplayString
	ACCESS	read-only
	STATUS	mandatory
	DESCRIPTION
	         "The battery type."
	::= {ups 9}

upsStatus OBJECT-TYPE
	SYNTAX	DisplayString
	ACCESS	read-only
	STATUS	mandatory
	DESCRIPTION
	         "The current UPS status string."
	::= {ups 10}

END
